real X;
real Y;
real X2;
real Y2;

real XF;
real YF;

int i=0;
int columnas=2;
int filas=2;
real gridb;

string Signal_[];
string Replicar_img = "<img src=\"replicar.png\">";
string namebrd;

if (board)
{
	board(B)
	{
		gridb = B.grid.distance;
		int Result = dlgDialog("Replicate Board ") 
			{
				dlgLabel("Created by: Albert Nissimoff");
				dlgPushButton("+OK") dlgAccept();
				dlgPushButton("-Cancelar"	) { if (dlgMessageBox("¿Estas Seguro?", "Si", "No") == 0) exit(0); } 
				
			};
		int haveButton = 1;
		dlgDialog("Panelizar") {
			dlgLabel("Digite os dados desejados:");
				if (haveButton)
					dlgPushButton("Procesar") dlgAccept();
				dlgPushButton("-Cancelar") { exit(0); }
				dlgLabel(Replicar_img, 1);
						dlgHBoxLayout 
				{
				dlgLabel("X:                            ");
				dlgIntEdit(columnas, 0, 250);
				}
				
				dlgHBoxLayout 
				{
				dlgLabel("Y:                            ");
				dlgIntEdit(filas, 0, 250);
				} 

				{
				dlgLabel("Xf:                            ");
				dlgRealEdit(XF, 0, 250);
				}
				
				dlgHBoxLayout 
				{
				dlgLabel("Yf:                            ");
				dlgRealEdit(YF, 0, 250);
				} 
			}; 

			string ulp_path;
			char bkslash = '/';
			int pos = strrchr(argv[0], bkslash);
			if (pos >= 0) {
				ulp_path = strsub(argv[0], 0, pos + 1);
			}
			
			output(ulp_path + "Panelizar.scr", "wt") {
				printf("display none;\n");
				printf("group;\n");
				printf("Layer 116 outlines;LAYER 125 _tnames;LAYER 126 _bnames;display none;display 125 126;group all;delete (c > 0 0);display all;set confirm yes;run Panelize_Names_Layers.ulp;grid mm;\n");
				printf("Group all;\n");
				printf("Cut (0 0);\n");
				printf("display none;display 125 126;group all;delete (c > 0 0);display all;");
				printf("EDIT _X%d.brd;\n",filas*columnas);
				printf("DRC LOAD C:\\Users\\Alb\\Desktop\\ControliD\\ACESSO-LEITOR\\HW-git\\leitorrf\\Hardware\\Leitor.dru;");
				printf("grid mm;\n");
				int z;
				for(int x_ = 0; x_ < columnas; x_++){
					for(int y_=0; y_ < filas; y_++){
						printf("paste  (%f %f)\n",x_*XF,y_*YF);
					} 
				}
				printf("display none;display 125 126;group all;change font vector;display all;");
				printf("set confirm off;grid on dots %f;\n",gridb);
			}
			exit("; SCR '" + ulp_path + "Panelizar.scr';\n");	  
		}
	}
else
{
	;
}
